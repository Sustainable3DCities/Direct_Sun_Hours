FME workspace ogckml_ogckml2shapefile_shapefile_2022_10_18.fmw

Parameters:
- DestDataset_SHAPEFILE =
- DestDataset_SHAPEFILE_11 =
- DestDataset_SHAPEFILE_12 =
- DestDataset_SHAPEFILE_13 =
- DestDataset_SHAPEFILE_14 =
- DestDataset_SHAPEFILE_15 =
- DestDataset_SHAPEFILE_16 =
- DestDataset_SHAPEFILE_17 =
- DestDataset_SHAPEFILE_18 =
- DestDataset_SHAPEFILE_19 =
- SourceDataset_OGCKML =
- SourceDataset_OGCKML_10 =
- SourceDataset_OGCKML_11 =
- SourceDataset_OGCKML_12 =
- SourceDataset_OGCKML_13 =
- SourceDataset_OGCKML_14 =
- SourceDataset_OGCKML_15 =
- SourceDataset_OGCKML_9 =

Readers:
- OGCKML_1: OGCKML from $(SourceDataset_OGCKML)
- OGCKML_2: OGCKML from $(SourceDataset_OGCKML_9)
- OGCKML_3: OGCKML from $(SourceDataset_OGCKML_13)
- OGCKML_4: OGCKML from $(SourceDataset_OGCKML_11)
- OGCKML_5: OGCKML from $(SourceDataset_OGCKML_15)
- OGCKML_6: OGCKML from $(SourceDataset_OGCKML_10)
- OGCKML_7: OGCKML from $(SourceDataset_OGCKML_12)
- OGCKML_8: OGCKML from $(SourceDataset_OGCKML_14)

Writers:
- SHAPEFILE_1: SHAPEFILE to $(DestDataset_SHAPEFILE) in SWEREF-99-TM
- SHAPEFILE_2: SHAPEFILE to $(DestDataset_SHAPEFILE_13) in SWEREF-99-TM
- SHAPEFILE_3: SHAPEFILE to $(DestDataset_SHAPEFILE_19) in SWEREF-99-TM
- SHAPEFILE_4: SHAPEFILE to $(DestDataset_SHAPEFILE_12) in SWEREF-99-TM
- SHAPEFILE_5: SHAPEFILE to $(DestDataset_SHAPEFILE_14) in SWEREF-99-TM
- SHAPEFILE_6: SHAPEFILE to $(DestDataset_SHAPEFILE_17) in SWEREF-99-TM
- SHAPEFILE_7: SHAPEFILE to $(DestDataset_SHAPEFILE_15) in SWEREF-99-TM
- SHAPEFILE_8: SHAPEFILE to $(DestDataset_SHAPEFILE_11) in SWEREF-99-TM
- SHAPEFILE_9: SHAPEFILE to $(DestDataset_SHAPEFILE_16) in SWEREF-99-TM
- SHAPEFILE_10: SHAPEFILE to $(DestDataset_SHAPEFILE_18) in SWEREF-99-TM

LocalCoordinateSystemSetter_6
    ORIGIN_CS = LL84
    ORIGIN_X = 12.9760701
    ORIGIN_Y = 55.5553507
    PROJECTION_TYPE = Equidistant (AZMED)
    PROJECTION_UNITS = Meters
    -> GeometryFilter_7
GeometryFilter_7
    BREAK_AGG = Yes
    GEOM_PORT_NAMES = Point Line Area Surface Solid Collection Null
    INSTANTIATE = Yes
    SURFACE -> facades (writer SHAPEFILE_3)
LocalCoordinateSystemSetter_2
    ORIGIN_CS = LL84
    ORIGIN_X = 12.9760701
    ORIGIN_Y = 55.5553507
    PROJECTION_TYPE = Equidistant (AZMED)
    PROJECTION_UNITS = Meters
    -> GeometryFilter_3
GeometryFilter_3
    BREAK_AGG = Yes
    GEOM_PORT_NAMES = Point Line Area Surface Solid Collection Null
    INSTANTIATE = Yes
    SURFACE -> building (writer SHAPEFILE_4)
LocalCoordinateSystemSetter_3
    ORIGIN_CS = LL84
    ORIGIN_X = 12.9760701
    ORIGIN_Y = 55.5553507
    PROJECTION_TYPE = Equidistant (AZMED)
    PROJECTION_UNITS = Meters
    -> GeometryFilter_2
GeometryFilter_2
    BREAK_AGG = Yes
    GEOM_PORT_NAMES = Point Line Area Surface Solid Collection Null
    INSTANTIATE = Yes
    SURFACE -> windows (writer SHAPEFILE_5)
LocalCoordinateSystemSetter_4
    ORIGIN_CS = LL84
    ORIGIN_X = 12.9760701
    ORIGIN_Y = 55.5553507
    PROJECTION_TYPE = Equidistant (AZMED)
    PROJECTION_UNITS = Meters
    -> GeometryFilter_4
GeometryFilter_4
    BREAK_AGG = Yes
    GEOM_PORT_NAMES = Point Line Area Surface Solid Collection Null
    INSTANTIATE = Yes
    SURFACE -> balcony_doors (writer SHAPEFILE_6)
LocalCoordinateSystemSetter_5
    ORIGIN_CS = LL84
    ORIGIN_X = 12.9760701
    ORIGIN_Y = 55.5553507
    PROJECTION_TYPE = Equidistant (AZMED)
    PROJECTION_UNITS = Meters
    -> GeometryFilter_8
GeometryFilter_8
    BREAK_AGG = Yes
    GEOM_PORT_NAMES = Point Line Area Surface Solid Collection Null
    INSTANTIATE = Yes
    SURFACE -> apertures (writer SHAPEFILE_7)
LocalCoordinateSystemSetter_7
    ORIGIN_CS = LL84
    ORIGIN_X = 12.9760701
    ORIGIN_Y = 55.5553507
    PROJECTION_TYPE = Equidistant (AZMED)
    PROJECTION_UNITS = Meters
    -> GeometryFilter_5
GeometryFilter_5
    BREAK_AGG = Yes
    GEOM_PORT_NAMES = Point Line Area Surface Solid Collection Null
    INSTANTIATE = Yes
    SURFACE -> balconies (writer SHAPEFILE_8)
LocalCoordinateSystemSetter_8
    ORIGIN_CS = LL84
    ORIGIN_X = 12.9760701
    ORIGIN_Y = 55.5553507
    PROJECTION_TYPE = Equidistant (AZMED)
    PROJECTION_UNITS = Meters
    -> GeometryFilter_6
GeometryFilter_6
    BREAK_AGG = Yes
    GEOM_PORT_NAMES = Point Line Area Surface Solid Collection Null
    INSTANTIATE = Yes
    SURFACE -> balcony_railing (writer SHAPEFILE_9)
LocalCoordinateSystemSetter_9
    ORIGIN_CS = LL84
    ORIGIN_X = 12.9760701
    ORIGIN_Y = 55.5553507
    PROJECTION_TYPE = Equidistant (AZMED)
    PROJECTION_UNITS = Meters
    -> GeometryFilter_9
GeometryFilter_9
    BREAK_AGG = Yes
    GEOM_PORT_NAMES = Point Line Area Surface Solid Collection Null
    INSTANTIATE = Yes
    SURFACE -> surroundings (writer SHAPEFILE_10)

Bookmark: facade models
Placemark (reader OGCKML_2)
    -> LocalCoordinateSystemSetter_6

Bookmark: Writer Feature Types
facades (writer SHAPEFILE_3)
building (writer SHAPEFILE_4)
windows (writer SHAPEFILE_5)
balcony_doors (writer SHAPEFILE_6)
apertures (writer SHAPEFILE_7)
balconies (writer SHAPEFILE_8)
balcony_railing (writer SHAPEFILE_9)
surroundings (writer SHAPEFILE_10)

Bookmark: building models
Placemark (reader OGCKML_1)
    -> LocalCoordinateSystemSetter_2

Bookmark: Windows
Placemark (reader OGCKML_4)
    -> LocalCoordinateSystemSetter_3

Bookmark: Balcony_doors
Placemark (reader OGCKML_5)
    -> LocalCoordinateSystemSetter_4

Bookmark: Apertures (windows & balcony doors)
Placemark (reader OGCKML_6)
    -> LocalCoordinateSystemSetter_5

Bookmark: Balconies
Placemark (reader OGCKML_3)
    -> LocalCoordinateSystemSetter_7

Bookmark: Balcony_railing
Placemark (reader OGCKML_7)
    -> LocalCoordinateSystemSetter_8

Bookmark: Surroundings
Placemark (reader OGCKML_8)
    -> LocalCoordinateSystemSetter_9
